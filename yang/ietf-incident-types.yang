module ietf-incident-types {
  yang-version "1.1";
  namespace "urn:ietf:params:xml:ns:yang:ietf-incident-types";
  prefix "int";

  import ietf-network {
    prefix nw;
    reference
      "RFC 8345: A YANG Data Model for Network Topologies";
  }

  organization
    "IETF OPSAWG Working Group";
  contact
    "WG Web:   <https://datatracker.ietf.org/wg/opsawg/>;
     WG List:  <mailto:opsawg@ietf.org>
     Author:   Chong Feng  <mailto:frank.fengchong@huawei.com>
     Author:   Tong Hu  <mailto:hutong@cmhi.chinamobile.com>
     Author:   Luis Miguel Contreras Murillo <mailto:
               luismiguel.contrerasmurillo@telefonica.com>
     Author :  Thomas Graf   <mailto:thomas.graf@swisscom.com>
     Author :  Qin Wu   <mailto:bill.wu@huawei.com>
     Author:   Chaode Yu   <mailto:yuchaode@huawei.com>
     Author:   Nigel Davis   <mailto:ndavis@ciena.com>";

  description
    "This module defines the identities and typedefs for
     incident management.

     Copyright (c) 2022 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).
     This version of this YANG module is part of RFC XXXX; see the
     RFC itself for full legal notices.  ";
  revision 2023-05-16 {
    description "initial version";
    reference "RFC XXX: Yang module for incident management.";
  }
  //identities
  identity incident-domain {
    description "The abstract identity to indicate the domain of
                 an incident.";
  }
  identity single-domain {
    base incident-domain;
    description "single domain.";
  }
  identity access {
    base single-domain;
    description "access domain.";
  }
  identity ran {
    base access;
    description "radio access network domain.";
  }
  identity transport {
    base single-domain;
    description "transport domain.";
  }
  identity otn {
    base transport;
    description "optical transport network domain.";
  }
  identity ip {
    base single-domain;
    description "ip domain.";
  }
  identity ptn {
    base ip;
    description "packet transport network domain.";
  }

  identity cross-domain {
    base incident-domain;
    description "cross domain.";
  }
  identity incident-category {
    description "The abstract identity for incident category.";
  }
  identity device {
    base incident-category;
    description "device category.";
  }
  identity power-enviorment {
    base device;
    description "power system category.";
  }
  identity device-hardware {
    base device;
    description "hardware of device category.";
  }
  identity device-software {
    base device;
    description "software of device category";
  }
  identity line {
    base device-hardware;
    description "line card category.";
  }
  identity maintenance {
    base incident-category;
    description "maintenance category.";
  }
  identity network {
    base incident-category;
    description "network category.";
  }
  identity protocol {
    base incident-category;
    description "protocol category.";
  }
  identity overlay {
    base incident-category;
    description "overlay category";
  }
  identity vm {
    base incident-category;
    description "vm category.";
  }

  //typedefs
  typedef incident-priority {
    type enumeration {
      enum critical {
        description "the incident MUST be handled immediately.";
      }
      enum high {
        description "the incident should be handled as soon as
                     possible.";
      }
      enum medium {
        description "network services are not affected, or the
                     services are slightly affected,but corrective
                     measures need to be taken.";
      }
      enum low {
        description "potential or imminent service-affecting
                     incidents are detected,but services are
                     not affected currently.";
      }
    }
    description "define the priority of incident.";
  }
  typedef node-ref {
    type leafref {
      path "/nw:networks/nw:network/nw:node/nw:node-id";
    }
    description "reference a network node.";
  }
}
